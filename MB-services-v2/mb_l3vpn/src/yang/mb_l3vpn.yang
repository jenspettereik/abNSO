module mb_l3vpn {

  namespace "http://example.com/mb_l3vpn";
  prefix mb_l3vpn;

  import ietf-inet-types {
    prefix inet;
  }
  import tailf-common {
    prefix tailf;
  }
  import tailf-ncs {
    prefix ncs;
  }
  import mb_core {
    prefix mb_core;
  }

  description
    "L3VPN service for mobile backhaul.";

  revision 2022-12-29 {
    description
      "vrf_name is key, which means that endpoints are added to the VPN service instance. Pattern added for interface_number. Enumeration added for interface_name";
  }

  revision 2022-12-21 {
    description
      "Initial revision.";
  }

  grouping endpoint_grouping {
    leaf interface_name {
      tailf:info "Interface name. For example FastEthernet.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
      }
    }
    leaf interface_number {
      tailf:info "Interface number. For example 0 or 1/0";
      type string {
        pattern "[0-9]{1,2}(/[0-9]{1,2}){1,4}";
      }
    }
    leaf ipv4_address {
      tailf:info "Local interface address.";
      type inet:ipv4-address;
    }
    leaf ipv4_mask {
      tailf:info "Local interface mask.";
      type inet:ipv4-address;
    }
  }

  augment /mb_core:mb {

    list mb_l3vpn {
      description "This is an RFS skeleton service";

      key vrf_name;
      leaf vrf_name {
        tailf:info "Unique VPN service id";
        tailf:cli-allow-range;
        type string;
      }

      uses ncs:service-data;
      ncs:servicepoint mb_l3vpn-servicepoint;

      /* leaf vrf_name {
        tailf:info "VRF Name. When this is a separate leaf ie not the key, endpoints can be added as separate service instances eg via POST API call";
        type string;
      } */
      list endpoint {
        key "id";
        leaf id {
          tailf:info "Endpoint identifier";
          type string;
        }
        leaf as_number {
          description "AS used within all VRF of the VPN, 29695";
          tailf:info "MPLS VPN AS number.";
          type uint32;
          default 29695;
        }
        leaf rd {
          type uint32;
          tailf:info "Route Distinguisher";
          mandatory true;
        }
        leaf vlan {
          type uint32;
          mandatory true;
        }
        container csr {
          leaf device {
            type leafref {
              path "/ncs:devices/ncs:device/ncs:name";
            }
          }
          container local {
            uses endpoint_grouping;
          }
          container link {
            uses endpoint_grouping;
          }
        }

        container er {
          leaf device {
            type leafref {
              path "/ncs:devices/ncs:device/ncs:name";
            }
          }
          container link {
            uses endpoint_grouping;
          }
        }
      }
    }
  }
}
