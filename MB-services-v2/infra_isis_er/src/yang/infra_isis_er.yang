module infra_isis_er {

  namespace "http://example.com/infra_isis_er";
  prefix infra_isis_er;

  import ietf-inet-types {
    prefix inet;
  }
  import tailf-common {
    prefix tailf;
  }
  import tailf-ncs {
    prefix ncs;
  }

  description
    "Infrastructure ISIS for Mobile Backhaul for ER devices. This service is used as RFS in an CFS-RFS setup. Alternatively the mb_infra_cfs does the device provisioning directly";

  revision 2022-12-21 {
    description
      "Initial revision.";
  }

  list infra_isis_er {
    description "This is an RFS skeleton service";

    key name;
    leaf name {
      tailf:info "Unique service id";
      tailf:cli-allow-range;
      type string;
    }

    uses ncs:service-data;
    ncs:servicepoint infra_isis_er-servicepoint;

    leaf device {
      type leafref {
        path "/ncs:devices/ncs:device/ncs:name";
      }
    }
    leaf instance {
      type string;
    }
    leaf maxwait {
      type uint32;
    }
    leaf max_lsp_lifetime {
      type uint32;
    }
    leaf interface_name {
      tailf:info "Interface name. For example FastEthernet.";
      type string;
    }
    leaf interface_number {
      tailf:info "Interface number. For example 0 or 1/0";
      type string;
    }
  }
}
