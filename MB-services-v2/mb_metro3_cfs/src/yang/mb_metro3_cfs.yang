module mb_metro3_cfs {

  namespace "http://example.com/mb_metro3_cfs";
  prefix mb_metro3_cfs;

  import ietf-inet-types {
    prefix inet;
  }
  import tailf-common {
    prefix tailf;
  }
  import tailf-ncs {
    prefix ncs;
  }
  import mb_core {
    prefix mb_core;
  }

  description
    "Metro3 CFS";

  revision 2022-12-21 {
    description
      "Initial revision.";
  }

  augment /mb_core:mb {

    list mb_metro3_cfs {
      description "This is an RFS skeleton service";

      key name;
      leaf name {
        tailf:info "Unique service id";
        tailf:cli-allow-range;
        type string;
      }

      uses ncs:service-data;
      ncs:servicepoint mb_metro3_cfs-servicepoint;

      leaf group {
        tailf:info "Group or Devices";
        type enumeration {
          enum Group;
          enum Device;
        }
        default Group;
      }

      leaf device_group_id {
        tailf:display-when "../group = 'Group'";
        tailf:info "Unique device-group id";
        type leafref {
          path "/ncs:devices/ncs:device-group/ncs:name";
        }
      }

      leaf-list device {
        tailf:info "leaf-list device is used if device group is not used, ie the group parameter needs to be set to 'Device'";
        tailf:display-when "../group = 'Device'";
        type leafref {
          path "/ncs:devices/ncs:device/ncs:name";
        }
      }

      leaf m3_area {
        tailf:info "Used in case the RR inventory is in the infra_metro3_rr RFS";
        type leafref {
          path "/mb_core:mb/mb_core:mb_inventory/mb_core:METRO3Areas/mb_core:METRO3Area/mb_core:metro3_area";
        }
      }
    }
  }
}
