module ba_communitysets {

  namespace "http://example.com/ba_communitysets";
  prefix ba_communitysets;

  import ietf-inet-types {
    prefix inet;
  }
  import tailf-common {
    prefix tailf;
  }
  import tailf-ncs {
    prefix ncs;
  }

  description
    "Bla bla...";

  revision 2023-02-07 {
    description
      "Initial revision.";
  }

  list ba_communitysets {
    description "This is an RFS skeleton service";

    key name;
    leaf name {
      tailf:info "Unique service id";
      tailf:cli-allow-range;
      type string;
    }

    uses ncs:service-data;
    ncs:servicepoint ba_communitysets-servicepoint;

    leaf device {
      type leafref {
        path "/ncs:devices/ncs:device/ncs:name";
      }
    }

    leaf community_set_umpls {
      type string;
    }
    leaf as_number {
      tailf:info "Autonomous System number eg 29695 set as default";
      type uint16;
      default 29695;
    }
    leaf set_number {
      tailf:info "For the community set";
      type uint16;
    }
  }
}
