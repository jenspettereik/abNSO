module inventory {

  namespace "http://example.com/inventory";
  prefix inventory;

  import ietf-inet-types {
    prefix inet;
  }
  import tailf-common {
    prefix tailf;
  }
  import tailf-ncs {
    prefix ncs;
  }

  description
    "Inventory for the BA L3VPN Service";

  revision 2023-01-31 {
    description
      "Initial revision.";
  }

  container inventory {

    container METRO3Areas {
      list METRO3Area {
        key metro3_area;
        leaf metro3_area {
          type string;
        }
        list RR {
          key agg_device;
          leaf agg_device {
            type leafref {
              path "/ncs:devices/ncs:device/ncs:name";
            }
          }
          leaf RR_ipv4_addr {
            tailf:info "IP address of the neighbor";
            type inet:ipv4-address;
          }
          leaf neighbor_group_name {
            tailf:info "Name of the neighbor group to which the RR belongs";
            type string;
            default "T-RR-NC";
          }
          leaf neighbor_description {
            tailf:info "Description of the neighbor RR";
            type string;
            default "### ALL iBGP SESSIONS ###";
          }
        }
      }
    }

    container prefix_sets {
      list prefix_set {
        key prefix_set_name;
        leaf prefix_set_name {
          type string;
        }
        list rpl_prefix_set {
          key prefix_set_ip;
          leaf prefix_set_ip {
            type inet:ipv4-address;
          }
          leaf prefix_set_mask1 {
            tailf:info "E.g. 16";
            type uint16;
          }
          leaf prefix_set_operator {
            tailf:info "E.g. le";
            type string;
          }
          leaf prefix_set_mask2 {
            tailf:info "E.g. 32";
            type uint16;
          }
        }
      }
    }

    container community_sets {
      list community_set {
        key community_set_name;
        leaf community_set_name {
          type string;
        }
        list rpl_community_set {
          key part1;
          leaf part1 {
            type uint16;
          }
          leaf part2 {
            type uint16;
          }
        }
      }
    }

    container qos_policy_maps {
      list qos_policy_map {
        key qos_policy_map_name;
        leaf qos_policy_map_name {
          type string;
        }
        leaf description {
          type string;
        }
        container policy_classes {
          list policy_class {
            key class_name;
            leaf class_name {
              type leafref {
                path "../../../../../qos_class_maps/qos_class_map/qos_class_map_name";
              }
            }
            leaf class_type {
              type enumeration {
                enum qos;
                enum traffic;
              }
            }
            list class_operation {
              key operation_name;
              leaf operation_name {
                tailf:info "Just any name";
                type string;
              }
              leaf class_operation_name {
                type enumeration {
                  enum set;
                  enum police;
                  enum shape;
                  enum bandwidth;
                  // The list is not complete
                }
              }
              leaf set_subject {
                tailf:display-when "../class_operation_name = 'set'";
                type enumeration {
                  enum qos-group;
                  enum traffic-class;
                  enum discard-class;
                  enum cos;
                  enum dscp;
                  // The list is not complete
                }
              }
              leaf police_subject {
                tailf:display-when "../class_operation_name = 'police'";
                type enumeration {
                  enum police_rate;
                  // The list is not complete
                }
              }
              leaf qos_group_value {
                tailf:display-when "../set_subject = 'qos-group'";
                type uint8 {
                  range "0..8";
                }
              }
              leaf traffic_class_value {
                tailf:display-when "../set_subject = 'traffic-class'";
                type uint8 {
                  range "0..8";
                }
              }
              leaf discard_class_value {
                tailf:display-when "../set_subject = 'discard-class'";
                type uint8 {
                  range "0..8";
                }
              }
              leaf police_value {
                tailf:display-when "../police_subject = 'police_rate'";
                type uint64;
              }
              leaf police_unit {
                tailf:display-when "../police_subject = 'police_rate'";
                type enumeration {
                  enum percent;
                  enum bps;
                  enum cellsps;
                  enum kbps;
                  enum mbps;
                  enum gbps;
                  enum pps;
                  enum per-million;
                  enum per-thousand;
                }
              }
            }
          }
        }
      }
    }

    container qos_class_maps {
      list qos_class_map {
        key qos_class_map_name;
        leaf qos_class_map_name {
          type string;
        }
        leaf match_statement {
          type enumeration {
            enum match-all;
            enum match-any;
            enum match-not;
          }
        }
        leaf description {
          type string;
        }
        container match_elements {
          list match_element {
            key match_subject;
            leaf match_subject {
              type enumeration {
                enum ipv4;
                enum traffic-class;
                enum destination-address;
                enum protocol;
                enum vlan;
                enum destination-port;
                enum mpls;
                enum qos-group;
                enum cos;
                enum dscp;
                enum precedence;
                // The list is not complete. Only the ones used by the use-case are enabled
              }
            }
            container mpls {
              tailf:display-when "../match_subject = 'mpls'";
              leaf mpls_subject1 {
                type enumeration {
                  enum experimental;
                  enum disposition;
                }
              }
              leaf mpls_subject2 {
                tailf:display-when "../mpls_subject1 = 'experimental'";
                type enumeration {
                  enum imposition;
                  enum topmost;
                }
              }
              list mpls_labels {
                key mpls_label;
                leaf mpls_label {
                  type uint8 {
                    range "1..7";
                  }
                }
              }
            }
            container dscp {
              tailf:display-when "../match_subject = 'dscp'";
              list dscp_values {
                key dscp_value;
                leaf dscp_value {
                  type enumeration {
                    enum af11;
                    enum af12;
                    enum af13;
                    enum af21;
                    enum af22;
                    enum af23;
                    enum af31;
                    enum af32;
                    enum af33;
                    enum af41;
                    enum af42;
                    enum af43;
                    enum cs1;
                    enum cs2;
                    enum cs3;
                    enum cs4;
                    enum cs5;
                    enum cs6;
                    enum cs7;
                    enum ef;
                    enum def;
                  }
                }
              }
            }
            container cos {
              tailf:display-when "../match_subject = 'cos'";
              list cos_values {
                key cos_value;
                leaf cos_value {
                  type uint8 {
                    range "1..7";
                  }
                }
              }
            }
          }
        }
      }
    }
  }
}
