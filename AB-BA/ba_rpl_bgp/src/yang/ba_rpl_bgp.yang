module ba_rpl_bgp {

  namespace "http://example.com/ba_rpl_bgp";
  prefix ba_rpl_bgp;

  import ietf-inet-types {
    prefix inet;
  }
  import tailf-common {
    prefix tailf;
  }
  import tailf-ncs {
    prefix ncs;
  }

  description
    "BGP Routing Policies";

  revision 2023-02-07 {
    description
      "Initial revision.";
  }

  list ba_rpl_bgp {
    description "This is an RFS skeleton service";

    key name;
    leaf name {
      tailf:info "Unique service id";
      tailf:cli-allow-range;
      type string;
    }

    uses ncs:service-data;
    ncs:servicepoint ba_rpl_bgp-servicepoint;

    leaf device {
      type leafref {
        path "/ncs:devices/ncs:device/ncs:name";
      }
    }

    leaf community_set_umpls {
      type string;
    }
    /* leaf as_number {
      tailf:info "Autonomous System number eg 29695 set as default";
      type uint16;
      default 29695;
    }
    leaf set_number {
      tailf:info "For the community set";
      type uint16;
    } */

    leaf prefix_set_umpls {
      type string;
    }
    /* leaf prefix_set_ip {
      type inet:ipv4-address;
    }
    leaf prefix_set_mask1 {
      tailf:info "E.g. 16";
      type uint16;
    }
    leaf prefix_set_operator {
      tailf:info "E.g. le";
      type string;
    }
    leaf prefix_set_mask2 {
      tailf:info "E.g. 32";
      type uint16;
    } */
  }
}
