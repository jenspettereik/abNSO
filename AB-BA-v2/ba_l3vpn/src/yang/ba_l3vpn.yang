module ba_l3vpn {

  namespace "http://example.com/ba_l3vpn";
  prefix ba_l3vpn;

  import ietf-inet-types {
    prefix inet;
  }
  import tailf-common {
    prefix tailf;
  }
  import tailf-ncs {
    prefix ncs;
  }
  import inventory {
    prefix inventory;
  }

  description
    "The Customer Facing Service CFS for doing BA L3VPN Services";

  revision 2023-06-16 {
    description
      "Implemented the eight point list, incl. Introduced ipsla_mgmt_address for Loopback100 and introduced the IPSLA rfs.";
  }

  revision 2023-04-02 {
    description
      "Introduced a name as service id, ie vrf_name is no longer the service key. Introduced the base configuration RFS, which configures all the remaining configuration not covered by the other RFSs";
  }

  revision 2023-02-24 {
    description
      "only_CSR added. Added support for VRF import and export route-targets";
  }

  revision 2023-02-18 {
    description
      "Community sets, prefix sets, policy maps and RPL's made static.";
  }

  revision 2023-01-31 {
    description
      "Initial revision.";
  }

  grouping endpoint_grouping {
    leaf interface_name {
      tailf:info "Interface name. For example FastEthernet.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
      }
    }
    leaf interface_number {
      tailf:info "Interface number. For example 0 or 1/0";
      type string {
        pattern "[0-9]{1,2}(/[0-9]{1,2}){1,4}";
      }
    }
    leaf ipv4_address {
      tailf:info "Local interface address.";
      type inet:ipv4-address;
    }
    leaf ipv4_mask {
      tailf:info "Local interface mask.";
      type inet:ipv4-address;
    }
  }

  list ba_l3vpn {
    description "This is an RFS skeleton service";

    // 8: gjør om sånn at vi bruker 1 vpn/vrf = 1 service. post kall for å bygge tjenste, patch kal for å legge på endepunkter
    /* key name;
    leaf name {
      tailf:info "Unique service id";
      tailf:cli-allow-range;
      type string;
    } */

    key vrf_name;     // According to point 8.
    leaf vrf_name {
      tailf:info "Unique VPN service id";
      type string;
      // mandatory true;      // According to point 8.
    }

    leaf only_CSR {
      tailf:info "true if only CSR should be configured, not ER and AGG. false if also ER and AGG should be configured.";
      type boolean;
      default false;
    }

    uses ncs:service-data;
    ncs:servicepoint ba_l3vpn-servicepoint;

    list endpoint {
      key "id";
      leaf id {
        tailf:info "Endpoint identifier. It should be the number of the mobile CSR, fx '03340'. It will be added to the hostname, so hostname will be fx 'mobile-03340-csr1'";
        type string;
      }
      leaf as_number {
        description "AS used within all VRF of the VPN, 29695";
        tailf:info "MPLS VPN AS number.";
        type uint32;
        default 29695;
      }
      leaf rd {
        type uint32;
        tailf:info "Route Distinguisher";
        mandatory true;
      }
      list imprti {
        key import_rt_index;
        leaf import_rt_index {
          type uint32;
          tailf:info "Index of the import Route Target";
        }
      }
      list exprti {
        key export_rt_index;
        leaf export_rt_index {
          type uint32;
          tailf:info "Index of the export Route Target";
        }
      }
      leaf vlan {
        type uint32;
        mandatory true;
      }
      container csr {
        leaf device {
          type leafref {
            path "/ncs:devices/ncs:device/ncs:name";
          }
        }
        container local {
          uses endpoint_grouping;
        }
        container link {
          uses endpoint_grouping;
        }
        /* leaf community_set_umpls {
          type leafref {
            path "/inventory:inventory/inventory:community_sets/inventory:community_set/inventory:community_set_name";
          }
        }
        leaf prefix_set_umpls {
          type leafref {
            path "/inventory:inventory/inventory:prefix_sets/inventory:prefix_set/inventory:prefix_set_name";
          }
        }
        leaf vrf_policy_map {
          type leafref {
            path "/inventory:inventory/inventory:qos_policy_maps/inventory:qos_policy_map/inventory:qos_policy_map_name";
          }
        }
        leaf uplink_policy_map {
          type leafref {
            path "/inventory:inventory/inventory:qos_policy_maps/inventory:qos_policy_map/inventory:qos_policy_map_name";
          }
        } */
        leaf mgmt_ipv4_address {
          tailf:info "IP address of a Loopback interface";
          type inet:ipv4-address;
        }
        leaf ipsla_mgmt_address {
          tailf:info "IP address of the Loopback interface used for IPSLA Mgmt";
          type inet:ipv4-address;
        }
        leaf police_value {
          tailf:info "Bandwidth to be policed on the VRF interface. This overwrites the value defined in inventory.";
          type uint64;
        }
        leaf police_unit {
          tailf:info "Unit for the bandwidth to be policed on the VRF interface. This overwrites the value defined in inventory.";
          type enumeration {
            enum percent;
            enum bps;
            enum cellsps;
            enum kbps;
            enum mbps;
            enum gbps;
            enum pps;
            enum per-million;
            enum per-thousand;
          }
        }
        /* leaf paths_route_policy {
          tailf:info "ex RPL-uMPLS_PIC_INSTALL";
          type string;
          default "RPL-uMPLS_PIC_INSTALL";
        }
        leaf networks_route_policy {
          tailf:info "ex RPL-uMPLS_ADVERTISE";
          type string;
          default "RPL-uMPLS_ADVERTISE";
        }
        leaf ng_route_policy_in {
          tailf:info "ex RPL-uMPLS_IN";
          type string;
          default "RPL-uMPLS_IN";
        }
        leaf ng_route_policy_out {
          tailf:info "ex RPL-uMPLS_OUT";
          type string;
          default "RPL-uMPLS_OUT";
        } */
        
        // 1: i steden for å lage inventory på METRO ring, så vil det i API kallet komme:
        // hostanvn/device navn på RR1 og RR2 (AGG1 og AGG2)
        // peer ip adresse på RR1 og RR2 (RR1 på AGG1 og AGG2)

        /* leaf m3_area {
          tailf:info "Get the list of RR neighbors for the metro area";
          type leafref {
            path "/inventory:inventory/inventory:METRO3Areas/inventory:METRO3Area/inventory:metro3_area";
          }
        } */
        leaf rr1_device_name {
          tailf:info "Device name of RR1";
          type leafref {
            path "/ncs:devices/ncs:device/ncs:name";
          }
        }
        leaf rr1_ipv4_address {
          tailf:info "IP address of RR1";
          type inet:ipv4-address;
        }
        leaf rr2_device_name {
          tailf:info "Device name of RR2";
          type leafref {
            path "/ncs:devices/ncs:device/ncs:name";
          }
        }
        leaf rr2_ipv4_address {
          tailf:info "IP address of RR2";
          type inet:ipv4-address;
        }
      }

      container er {
        leaf device {
          type leafref {
            path "/ncs:devices/ncs:device/ncs:name";
          }
        }
        /* leaf downlink_policy_map {
          type leafref {
            path "/inventory:inventory/inventory:qos_policy_maps/inventory:qos_policy_map/inventory:qos_policy_map_name";
          }
        } */
        container link {
          uses endpoint_grouping;
        }
      }
    }
  }
}
