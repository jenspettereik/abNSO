module ba_base_conf {

  namespace "http://example.com/ba_base_conf";
  prefix ba_base_conf;

  import ietf-inet-types {
    prefix inet;
  }
  import tailf-common {
    prefix tailf;
  }
  import tailf-ncs {
    prefix ncs;
  }

  description
    "All the remaining base configuration, which is not covered by the other RFSs, is configured by this service";

  revision 2023-04-02 {
    description
      "Initial revision.";
  }

  list ba_base_conf {
    description "This is an RFS skeleton service";

    key name;
    leaf name {
      tailf:info "Unique service id";
      tailf:cli-allow-range;
      type string;
    }

    uses ncs:service-data;
    ncs:servicepoint ba_base_conf-servicepoint;

    container base_conf {
      container csr {
        leaf device {
          type leafref {
            path "/ncs:devices/ncs:device/ncs:name";
          }
        }
        leaf hostname {
          tailf:info "Name of the device fx mobile-03340-csr1";
          type string;
        }
        leaf mgmt_ipv4_address {
          tailf:info "IP address of Loopback interface 0";
          type inet:ipv4-address;
        }
        leaf ipsla_mgmt_address {
          tailf:info "IP address of the Loopback interface used for IPSLA Mgmt";
          type inet:ipv4-address;
        }
      }
    }
  }
}
