module ba_qos {

  namespace "http://example.com/ba_qos";
  prefix ba_qos;

  import ietf-inet-types {
    prefix inet;
  }
  import tailf-common {
    prefix tailf;
  }
  import tailf-ncs {
    prefix ncs;
  }
  import inventory {
    prefix inventory;
  }

  description
    "Bla bla...";

  revision 2023-02-16 {
    description
      "Initial revision.";
  }

  list ba_qos {
    description "This is an RFS skeleton service";

    key name;
    leaf name {
      tailf:info "Unique service id";
      tailf:cli-allow-range;
      type string;
    }

    uses ncs:service-data;
    ncs:servicepoint ba_qos-servicepoint;

    leaf policy_map_name {
      type leafref {
        path "/inventory:inventory/inventory:qos_policy_maps/inventory:qos_policy_map/inventory:qos_policy_map_name";
      }
    }
    leaf police_value {
      tailf:info "Bandwidth to be policed on the VRF interface";
      type uint64;
    }
    leaf police_unit {
      tailf:info "Unit for the bandwidth to be policed on the VRF interface";
      type enumeration {
        enum percent;
        enum bps;
        enum cellsps;
        enum kbps;
        enum mbps;
        enum gbps;
        enum pps;
        enum per-million;
        enum per-thousand;
      }
    }

    leaf device {
      type leafref {
        path "/ncs:devices/ncs:device/ncs:name";
      }
    }
  }
}
