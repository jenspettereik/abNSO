module ba_isis {

  namespace "http://example.com/ba_isis";
  prefix ba_isis;

  import ietf-inet-types {
    prefix inet;
  }
  import tailf-common {
    prefix tailf;
  }
  import tailf-ncs {
    prefix ncs;
  }

  description
    "RFS for ISIS configuration of ER CSR pairs";

  revision 2023-02-24 {
    description
      "only_CSR added.";
  }

  revision 2023-02-02 {
    description
      "Initial revision.";
  }

  grouping interface_grouping {
    leaf interface_name {
      tailf:info "Interface name. For example TenGigE.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
      }
    }
    leaf interface_number {
      tailf:info "Interface number. For example 0 or 1/0";
      type string {
        pattern "[0-9]{1,2}(/[0-9]{1,2}){1,4}";
      }
    }
    leaf ipv4_address {
      tailf:info "Local interface address.";
      type inet:ipv4-address;
    }
    leaf ipv4_mask {
      tailf:info "Local interface mask.";
      type inet:ipv4-address;
    }
    /* leaf interface_description {
      type string;
    } */
  }

  list ba_isis {
    description "This is an RFS skeleton service";

    key name;
    leaf name {
      tailf:info "Unique service id";
      tailf:cli-allow-range;
      type string;
    }

    leaf only_CSR {
      tailf:info "true if only CSR should be configured, not ER and AGG. false if also ER and AGG should be configured.";
      type boolean;
      default false;
    }

    leaf net_id {
      tailf:info "ISIS NET ID. Format sample 49.0002.2131.6711.5202.00";
      type string;
    }

    uses ncs:service-data;
    ncs:servicepoint ba_isis-servicepoint;

    container isis {

      container csr {
        leaf device {
          type leafref {
            path "/ncs:devices/ncs:device/ncs:name";
          }
        }
        container isis_interface {
          uses interface_grouping;
        }
      }

      container er {
        leaf device {
          type leafref {
            path "/ncs:devices/ncs:device/ncs:name";
          }
        }
        container isis_interface {
          uses interface_grouping;
        }
      }
    }
  }
}
