module ba_interface_qos {

  namespace "http://example.com/ba_interface_qos";
  prefix ba_interface_qos;

  import ietf-inet-types {
    prefix inet;
  }
  import tailf-common {
    prefix tailf;
  }
  import tailf-ncs {
    prefix ncs;
  }

  description
    "RFS for adding QoS policy to interfaces";

  revision 2023-02-16 {
    description
      "Initial revision.";
  }

  grouping interface_grouping {
    leaf interface_name {
      tailf:info "Interface name. For example TenGigE.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
      }
    }
    leaf interface_number {
      tailf:info "Interface number. For example 0 or 1/0";
      type string {
        pattern "[0-9]{1,2}(/[0-9]{1,2}){1,4}";
      }
    }
  }

  list ba_interface_qos {
    description "This is an RFS skeleton service";

    key name;
    leaf name {
      tailf:info "Unique service id";
      tailf:cli-allow-range;
      type string;
    }

    uses ncs:service-data;
    ncs:servicepoint ba_interface_qos-servicepoint;

    leaf device {
      type leafref {
        path "/ncs:devices/ncs:device/ncs:name";
      }
    }

    leaf policy_map_name {
      type string;
    }
    container interface {
      uses interface_grouping;
    }
  }
}
