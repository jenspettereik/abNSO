module ba_rpl_bgp {

  namespace "http://example.com/ba_rpl_bgp";
  prefix ba_rpl_bgp;

  import ietf-inet-types {
    prefix inet;
  }
  import tailf-common {
    prefix tailf;
  }
  import tailf-ncs {
    prefix ncs;
  }

  description
    "BGP Routing Policies";

  revision 2023-02-07 {
    description
      "Initial revision.";
  }

  list ba_rpl_bgp {
    description "This is an RFS skeleton service";

    key name;
    leaf name {
      tailf:info "Unique service id";
      tailf:cli-allow-range;
      type string;
    }

    uses ncs:service-data;
    ncs:servicepoint ba_rpl_bgp-servicepoint;

    leaf device {
      type leafref {
        path "/ncs:devices/ncs:device/ncs:name";
      }
    }
  }
}
