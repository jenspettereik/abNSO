module ba_bgp {

  namespace "http://example.com/ba_bgp";
  prefix ba_bgp;

  import ietf-inet-types {
    prefix inet;
  }
  import tailf-common {
    prefix tailf;
  }
  import tailf-ncs {
    prefix ncs;
  }
  import inventory {
    prefix inventory;
  }

  description
    "RFS to do BGP configuration";

  revision 2023-06-20 {
    description
      "1: i steden for å lage inventory på METRO ring, så vil det i API kallet komme: hostanvn/device navn på RR1 og RR2 (AGG1 og AGG2), peer ip adresse på RR1 og RR2 (RR1 på AGG1 og AGG2)";
  }

  revision 2023-02-24 {
    description
      "only_CSR added.";
  }

  revision 2023-02-18 {
    description
      "Community sets, prefix sets, policy maps and RPL's made static.";
  }

  revision 2023-02-01 {
    description
      "Initial revision.";
  }

  list ba_bgp {
    description "This is an RFS skeleton service";

    key name;
    leaf name {
      tailf:info "Unique service id";
      tailf:cli-allow-range;
      type string;
    }

    uses ncs:service-data;
    ncs:servicepoint ba_bgp-servicepoint;

    leaf only_CSR {
      tailf:info "true if only CSR should be configured, not ER and AGG. false if also ER and AGG should be configured.";
      type boolean;
      default false;
    }

    leaf as_number {
      tailf:info "Autonomous System number eg 29695 set as default";
      type uint16;
      default 29695;
    }
        // 1: i steden for å lage inventory på METRO ring, så vil det i API kallet komme:
        // hostanvn/device navn på RR1 og RR2 (AGG1 og AGG2)
        // peer ip adresse på RR1 og RR2 (RR1 på AGG1 og AGG2)

    /* leaf m3_area {
      tailf:info "Get the list of RR neighbors for the metro area";
      type leafref {
        path "/inventory:inventory/inventory:METRO3Areas/inventory:METRO3Area/inventory:metro3_area";
      }
    } */

    container bgp {

      container csr {
        leaf device {
          type leafref {
            path "/ncs:devices/ncs:device/ncs:name";
          }
        }
        leaf mgmt_ipv4_address {
          tailf:info "IP address of a Loopback interface";
          type inet:ipv4-address;
        }
        leaf rr1_device_name {
          tailf:info "Device name of RR1";
          type leafref {
            path "/ncs:devices/ncs:device/ncs:name";
          }
        }
        leaf rr1_ipv4_address {
          tailf:info "IP address of RR1";
          type inet:ipv4-address;
        }
        leaf rr2_device_name {
          tailf:info "Device name of RR2";
          type leafref {
            path "/ncs:devices/ncs:device/ncs:name";
          }
        }
        leaf rr2_ipv4_address {
          tailf:info "IP address of RR2";
          type inet:ipv4-address;
        }
      }
    }
  }
}
