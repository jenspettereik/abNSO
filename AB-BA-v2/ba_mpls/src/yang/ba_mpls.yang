module ba_mpls {

  namespace "http://example.com/ba_mpls";
  prefix ba_mpls;

  import ietf-inet-types {
    prefix inet;
  }
  import tailf-common {
    prefix tailf;
  }
  import tailf-ncs {
    prefix ncs;
  }
  import inventory {
    prefix inventory;
  }

  description
    "Bla bla...";

  revision 2023-02-24 {
    description
      "only_CSR added.";
  }

  revision 2023-02-01 {
    description
      "Initial revision.";
  }

  list ba_mpls {
    description "This is an RFS skeleton service";

    key name;
    leaf name {
      tailf:info "Unique service id";
      tailf:cli-allow-range;
      type string;
    }

    uses ncs:service-data;
    ncs:servicepoint ba_mpls-servicepoint;

    leaf only_CSR {
      tailf:info "true if only CSR should be configured, not ER and AGG. false if also ER and AGG should be configured.";
      type boolean;
      default false;
    }

    leaf acl_name {
      tailf:info "The ACL to be used with mpls";
      type leafref {
        path "/inventory:inventory/inventory:access_lists/inventory:access_list/inventory:acl_name";
      }
      default "MPLS_LOOPBACKS";   // This ACL must be present in the inventory!!
    }

    container mpls {
      container csr {
        leaf device {
          type leafref {
            path "/ncs:devices/ncs:device/ncs:name";
          }
        }
        leaf mgmt_ipv4_address {
          type inet:ipv4-address;
        }        
        leaf interface_name {
          type enumeration {
            enum TenGigE;
            enum GigabitEthernet;
          } 
        }  
        leaf interface_number {
          tailf:info "Metro interface number eg 0/0/0/21";
          type string {
            pattern "[0-9]{1,2}(/[0-9]{1,2}){1,4}";
          }
        }
      }
      container er {
        leaf device {
          type leafref {
            path "/ncs:devices/ncs:device/ncs:name";
          }
        }
        leaf interface_name {
          type enumeration {
            enum TenGigE;
            enum GigabitEthernet;
          } 
        }  
        leaf interface_number {
          tailf:info "Metro interface number eg 0/0/0/21";
          type string {
            pattern "[0-9]{1,2}(/[0-9]{1,2}){1,4}";
          }
        }
      }
    }
  }
}
