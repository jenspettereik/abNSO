module inventory {

  namespace "http://example.com/inventory";
  prefix inventory;

  import ietf-inet-types {
    prefix inet;
  }
  import tailf-common {
    prefix tailf;
  }
  import tailf-ncs {
    prefix ncs;
  }

  description
    "Inventory for the BA L3VPN Service";

  revision 2023-02-24 {
    description
      "Policy maps section updated to be able to handle a nested policy map.";
  }

  revision 2023-01-31 {
    description
      "Initial revision.";
  }

  container inventory {

    container METRO3Areas {
      list METRO3Area {
        key metro3_area;
        leaf metro3_area {
          type string;
        }
        list RR {
          key agg_device;
          leaf agg_device {
            type leafref {
              path "/ncs:devices/ncs:device/ncs:name";
            }
          }
          leaf RR_ipv4_addr {
            tailf:info "IP address of the neighbor";
            type inet:ipv4-address;
          }
          leaf neighbor_group_name {
            tailf:info "Name of the neighbor group to which the RR belongs";
            type string;
            default "T-RR-NC";
          }
          leaf neighbor_description {
            tailf:info "Description of the neighbor RR";
            type string;
            default "### ALL iBGP SESSIONS ###";
          }
        }
      }
    }

    container prefix_sets {
      list prefix_set {
        key prefix_set_name;
        leaf prefix_set_name {
          type string;
        }
        list rpl_prefix_set {
          key prefix_set_ip;
          leaf prefix_set_ip {
            type inet:ipv4-address;
          }
          leaf prefix_set_mask1 {
            tailf:info "E.g. 16";
            type uint16;
          }
          leaf prefix_set_operator {
            tailf:info "E.g. le";
            type string;
          }
          leaf prefix_set_mask2 {
            tailf:info "E.g. 32";
            type uint16;
          }
        }
      }
    }

    container community_sets {
      list community_set {
        key community_set_name;
        leaf community_set_name {
          type string;
        }
        list rpl_community_set {
          key part2;
          leaf part1 {
            type uint16;
          }
          leaf part2 {
            type uint16;
          }
        }
      }
    }

    // The access_lists inventory does not at all cover all access-list options in IOS-XR!!
    container access_lists {
      list access_list {
        key acl_name;
        leaf acl_name {
          type string;
        }
        list sequence {
          key sequence_number;
          leaf sequence_number {
            type uint16;
          }
          leaf permit_or_deny {
            type enumeration {
              enum permit;
              enum deny;
            }
          }
          leaf protocol {
            type enumeration { // The list is not complete!!
              enum ipv4;
              enum tcp;
              enum udp;
            }
          }
          list statements {
            key subject;
            leaf subject {
              type enumeration { // The list is not complete!!
                enum source;
                enum destination;
              }
            }
            leaf scope {
              type enumeration { // The list is not complete!!
                enum any;
                enum address;
                enum host;
              }
            }
            leaf ipv4_addr {
              tailf:display-when "../scope != 'any'";
              type inet:ipv4-address;
            }
            leaf prefix-length {
              tailf:display-when "../scope = 'address'";
              type uint16;
            }
          }
        }
      }
    }

    container qos_policy_maps {
      list qos_policy_map {
        key qos_policy_map_name;
        leaf qos_policy_map_name {
          type string;
        }
        leaf description {
          type string;
        }
        container policy_classes {
          list policy_class {
            key class_name;
            leaf class_name {
              type leafref {
                path "../../../../../qos_class_maps/qos_class_map/qos_class_map_name";
              }
            }
            leaf class_type {
              type enumeration {
                enum qos;
                enum traffic;
              }
            }
            list class_operation {
              key operation_name;
              leaf operation_name {
                tailf:info "Just any name";
                type string;
              }
              leaf class_operation_name {
                type enumeration {
                  enum set;
                  enum police;
                  enum shape;
                  enum bandwidth;
                  enum service-policy;
                  // The list is not complete
                }
              }
              leaf service_policy {
                tailf:display-when "../class_operation_name = 'service-policy'";
                type leafref {
                  path "../../../../../../qos_policy_maps/qos_policy_map/qos_policy_map_name";
                }
              }
              leaf set_subject {
                tailf:display-when "../class_operation_name = 'set'";
                type enumeration {
                  enum qos-group;
                  enum traffic-class;
                  enum discard-class;
                  enum cos;
                  enum dscp;
                  // The list is not complete
                }
              }
              leaf police_subject {
                tailf:display-when "../class_operation_name = 'police'";
                type enumeration {
                  enum police_rate;
                  // The list is not complete
                }
              }
              leaf qos_group_value {
                tailf:display-when "../set_subject = 'qos-group'";
                type uint8 {
                  range "0..8";
                }
              }
              leaf traffic_class_value {
                tailf:display-when "../set_subject = 'traffic-class'";
                type uint8 {
                  range "0..8";
                }
              }
              leaf discard_class_value {
                tailf:display-when "../set_subject = 'discard-class'";
                type uint8 {
                  range "0..8";
                }
              }
              leaf police_value {
                tailf:display-when "../police_subject = 'police_rate'";
                type uint64;
              }
              leaf police_unit {
                tailf:display-when "../police_subject = 'police_rate'";
                type enumeration {
                  enum percent;
                  enum bps;
                  enum cellsps;
                  enum kbps;
                  enum mbps;
                  enum gbps;
                  enum pps;
                  enum per-million;
                  enum per-thousand;
                }
              }
            }
          }
        }
      }
    }

    container qos_class_maps {
      list qos_class_map {
        key qos_class_map_name;
        leaf qos_class_map_name {
          type string;
        }
        leaf match_statement {
          type enumeration {
            enum match-all;
            enum match-any;
            enum match-not;
          }
        }
        leaf description {
          type string;
        }
        container match_elements {
          list match_element {
            key match_subject;
            leaf match_subject {
              type enumeration {
                enum ipv4;
                enum traffic-class;
                enum destination-address;
                enum protocol;
                enum vlan;
                enum destination-port;
                enum mpls;
                enum qos-group;
                enum cos;
                enum dscp;
                enum precedence;
                // The list is not complete. Only the ones used by the use-case are enabled
              }
            }
            container mpls {
              tailf:display-when "../match_subject = 'mpls'";
              leaf mpls_subject1 {
                type enumeration {
                  enum experimental;
                  enum disposition;
                }
              }
              leaf mpls_experimental {
                tailf:display-when "../mpls_subject1 = 'experimental'";
                type enumeration {
                  enum imposition;
                  enum topmost;
                }
              }
              list mpls_labels {
                // tailf:display-when "../mpls_subject1 = 'experimental'";
                key mpls_label;
                leaf mpls_label {
                  type uint8 {
                    range "1..7";
                  }
                }
              }
              leaf mpls_disposition {
                tailf:display-when "../mpls_subject1 = 'disposition'";
                type enumeration {
                  enum access-group;
                  enum class-map;
                }
              }
              leaf mpls_disposition_af {
                tailf:display-when "../mpls_subject1 = 'disposition'";
                type enumeration {
                  enum ipv4;
                  enum ipv6;
                }
              }
              leaf disposition_string {
                tailf:display-when "../mpls_subject1 = 'disposition'";
                type string;
              }
            }
            container dscp {
              tailf:display-when "../match_subject = 'dscp'";
              list dscp_values {
                key dscp_value;
                leaf dscp_value {
                  type enumeration {
                    enum af11;
                    enum af12;
                    enum af13;
                    enum af21;
                    enum af22;
                    enum af23;
                    enum af31;
                    enum af32;
                    enum af33;
                    enum af41;
                    enum af42;
                    enum af43;
                    enum cs1;
                    enum cs2;
                    enum cs3;
                    enum cs4;
                    enum cs5;
                    enum cs6;
                    enum cs7;
                    enum ef;
                    enum def;
                  }
                }
              }
            }
            container cos {
              tailf:display-when "../match_subject = 'cos'";
              list cos_values {
                key cos_value;
                leaf cos_value {
                  type uint8 {
                    range "1..7";
                  }
                }
              }
            }
            container vlan {
              tailf:display-when "../match_subject = 'vlan'";
              list vlan_ids {
                key vlan_id;
                leaf vlan_id {
                  type uint16 {
                    range "1..4095";
                  }
                }
              }
            }
          }
        }
      }
    }

    container ipsla_operations {
      list ipsla_operation {
        key operation_tag;
        leaf operation_tag {
          tailf:info "Here only the last part of the tag should be defined, fx 'best-effort-echo'. The hostname will be added by the python logic.";
          type string;
        }
        leaf operation_number {
          type uint8;
          mandatory true;
        }
        leaf operation_type {
          type enumeration {
            enum udp;
            enum icmp;
            enum mpls;
          }
          mandatory true;
        }
        leaf udp_operation_type {
          tailf:info "If udp is selected as operation_type, select if it should be echo or jitter.";
          tailf:display-when "../operation_type = 'udp'";
          type enumeration {
            enum echo;
            enum jitter;
          }
        }
        leaf icmp_operation_type {
          tailf:info "If icmp is selected as operation_type, select between three. NB: ICMP is not implemented in template!!";
          tailf:display-when "../operation_type = 'icmp'";
          type enumeration {
            enum echo;
            enum path-echo;
            enum path-jitter;
          }
        }
        leaf mpls_operation_type {
          tailf:display-when "../operation_type = 'mpls'";
          tailf:info "If mpls is selected as operation_type, select lsp. NB: MPLS is not implemented in template!!";
          type enumeration {
            enum lsp;
          }
        }
        container jitter_options {
          tailf:info "If udp jitter is selected, you have the option to set packet and/or statistics values.";
          tailf:display-when "../udp_operation_type = 'jitter'";
          container packet {
            leaf set_packet {
              type boolean;
              default false;
            }
            leaf count {
              type uint8;
            }
            leaf interval {
              type uint32;
            }
          }
          container statistics {
            leaf set_stats {
              type boolean;
              default false;
            }
            leaf buckets {
              type uint8 {
                range 1..100;
              }
            }
            leaf interval_time {
              type uint32;
            }
          }
        }
        leaf vrf {
          type string;
        }
        leaf source_address {
          tailf:info "Source address. No matter what you set it to in this inventory, it will be replaced by the ipsla_mgmt_address - Loopback100 address";
          type inet:ipv4-address;
        }
        leaf set_source_port {
          tailf:info "If the source port is not needed, please set this to false. If you define source port, you do not need to touch set_source_port. Default value is true.";
          type boolean;
          default true;
        }
        leaf source_port {
          type uint16;
          default 0;
        }
        leaf destination_address {
          tailf:info "Destination address. Destination ip is static";
          type inet:ipv4-address;
          default 10.254.1.1;
        }
        leaf set_destination_port {
          tailf:info "If the destination port is not needed, please set this to false. If you define destination port, you do not need to touch set_destination_port. Default value is true.";
          type boolean;
          default true;
        }
        leaf destination_port {
          type uint16;
          default 0;
        }
        container tos_or_not {
          leaf set_tos {
            tailf:info "Please select if tos must be applied.";
            type boolean;
          }
          leaf tos {
            type uint8;
          }
        }
        leaf frequency {
          type uint16;
        }
      }
    }
  }
}
