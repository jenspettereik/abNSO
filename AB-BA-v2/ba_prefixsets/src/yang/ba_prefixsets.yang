module ba_prefixsets {

  namespace "http://example.com/ba_prefixsets";
  prefix ba_prefixsets;

  import ietf-inet-types {
    prefix inet;
  }
  import tailf-common {
    prefix tailf;
  }
  import tailf-ncs {
    prefix ncs;
  }

  description
    "Bla bla...";

  revision 2023-02-07 {
    description
      "Initial revision.";
  }

  list ba_prefixsets {
    description "This is an RFS skeleton service";

    key name;
    leaf name {
      tailf:info "Unique service id";
      tailf:cli-allow-range;
      type string;
    }

    uses ncs:service-data;
    ncs:servicepoint ba_prefixsets-servicepoint;

    leaf device {
      type leafref {
        path "/ncs:devices/ncs:device/ncs:name";
      }
    }
    leaf set_name {
      type string;
      default "PFX-uMPLS_LOOPBACKS";
    }
  }
}
